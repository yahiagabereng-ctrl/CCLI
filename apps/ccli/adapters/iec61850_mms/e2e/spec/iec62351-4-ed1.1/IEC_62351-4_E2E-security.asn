E2E-Security {iso(1) standard(0) iec62351(62351) part4(4) modules(0) e2e-security(1)
  version1(1)}
DEFINITIONS IMPLICIT TAGS ::=
BEGIN

IMPORTS

  ApplData
    FROM Virtual-API
      {iso(1) standard(0) iec62351(62351) part4(4) modules(0) virtual-API(2) version1(1)} ;

-- ApplData ::= SEQUENCE{}

HandshakeReq ::= SEQUENCE {
  pp        NMTOKEN,
  tbs       SEQUENCE {
    token1    ClearToken1,
    applData  ApplData OPTIONAL,
    ... },
  sign      Signature }

NMTOKEN ::= UTF8String (FROM(
  {0, 0, 0, 32} .. {0, 0, 215, 255} |
  {0, 0, 224, 0} .. {0, 0, 255, 253} |
  {0, 1, 0, 0} .. {0, 16, 255, 253}))

HandshakeAcc ::= SEQUENCE {
  tbs SEQUENCE {
    token1    ClearToken1,
    applData  ApplData OPTIONAL,
    ... },
  sign      Signature }

ApplicationReject ::= SEQUENCE {
  tbs SEQUENCE {
    token3    ClearToken3,
    applData  ApplData,
    ... },
  sign      Signature } 

HandshakeSecReject ::= SEQUENCE {
  tbs SEQUENCE {
    token3    ClearToken3,
    diag      HandshakeDiagnostics OPTIONAL,
    ... },
  sign      Signature }

HandshakeSecAbort ::= SEQUENCE {
  tbs SEQUENCE {
    token3    ClearToken3,
    diag      HandshakeDiagnostics OPTIONAL,
    ... },
  sign      Signature }

DtSecAbort ::= SEQUENCE {
  tbs SEQUENCE {
    token3    ClearToken3,
    diag      DtDiagnostics OPTIONAL,
    ... },
  sign      Signature }

ApplAbort ::= SEQUENCE {
  tbs SEQUENCE {
    token3    ClearToken3,
    applData  ApplData OPTIONAL,
    ... },
  sign      Signature }

ReleaseReq ::= SEQUENCE {
  tbs SEQUENCE {
    token3    ClearToken3,
    ... },
  sign      Signature }

ReleaseRsp ::= SEQUENCE {
  tbs SEQUENCE {
    token3    ClearToken3,
    ... },
  sign      Signature }

ClearTransfer ::= SEQUENCE {
  tbp SEQUENCE {
    token2    ClearToken2,
    applData  ApplData,
    ... },
  auth      Authenticator }

EncrTransfer ::= SEQUENCE {
  tbp SEQUENCE {
    token2    ClearToken2,
    applData  Encrypted-ApplData,
    ... },
  auth      Authenticator OPTIONAL }

Encrypted-ApplData ::= OCTET STRING
-- Shall be the result of the encryption of the encoded ApplData

ClearToken1 ::= SEQUENCE {
  sigAlg         AlgorithmIdentifier {{SupportedSignatureAlgorithms}},
  pkCert         PKCert,
  certPath       CertPath OPTIONAL,
  version        Version DEFAULT {v1},
  assoID         AssoID,
  dHKey          DiffieHellmanSet,
  hmac           AlgorithmIdentifier {{SupportedHmacAlgorithms}},
  time           TimeStamp,
  encr-mode      CHOICE {
    aea            SEQUENCE SIZE (1..MAX) OF
      algo           AlgorithmIdentifier {{Supported-AEA-algorithms}},
    non-aea    [0] SEQUENCE {
      encr       [0] SEQUENCE SIZE (1..MAX) OF
        algo           AlgorithmIdentifier {{Supported-encrypt-algorithms}} OPTIONAL,
      icvAlgID   [1] SET SIZE (1..MAX) OF
        algo           AlgorithmIdentifier {{Supported-ICV-Algorithms}} },
    ... },
  confParams     ConfidentialityParms,
  attCert        ACert OPTIONAL,
  ... }

SupportedHmacAlgorithms ALGORITHM ::= { ... }

Version ::= BIT STRING {
  v1 (0)  -- version 1
  }

AssoID ::= NMTOKEN
  (PATTERN "(\d#(1,3):\d#(1,3))|(\d#(1,3))")

TimeStamp ::= GeneralizedTime

Supported-AEA-algorithms ALGORITHM ::= { ... }

Supported-encrypt-algorithms ALGORITHM ::= { aes256-CBC }

aes128-CBC ALGORITHM ::= {
  PARMS         AES-InitializationVector
  IDENTIFIED BY id-aes128-CBC }

aes256-CBC ALGORITHM ::= {
  PARMS         AES-InitializationVector
  IDENTIFIED BY id-aes256-CBC }

AES-InitializationVector ::= OCTET STRING (SIZE (16))

aes OBJECT IDENTIFIER ::= { joint-iso-itu-t(2) country(16) us(840)organization(1)
  gov(101) csor(3) nistAlgorithm(4) aes(1) }

id-aes128-CBC OBJECT IDENTIFIER ::= { aes 2 }

id-aes256-CBC OBJECT IDENTIFIER ::= { aes 42 }

PKCert ::= OCTET STRING
--  (CONTAINING Certificate ENCODED BY der)

ACert ::= OCTET STRING
--  (CONTAINING AttributeCertificate ENCODED BY der)

Supported-ICV-Algorithms ALGORITHM ::= { ... }

SupportedSignatureAlgorithms ALGORITHM ::= { ... }

DiffieHellmanSet ::= SEQUENCE {
  groupId     INTEGER,     -- Group identifier
  dhPublicKey DhPublicKey,
  ... }

DhPublicKey ::= OCTET STRING (SIZE(1..MAX))

ConfidentialityParms ::= BIT STRING {
  tlsProtected   (0),
  applProtected  (1),   -- end-to-end application level enc
  vpn            (2) }  -- out-of-current scope

CertPath ::= SEQUENCE SIZE (1..MAX) OF
  pkCert PKCert

ClearToken2 ::= SEQUENCE {
  version         Version DEFAULT {v1},
  assoID          AssoID,
  time            TimeStamp,
  seq             SequenceNumber,
  iv         [0]  InitializationVector OPTIONAL,  -- IV for AES encryption
  rekey      [1]  DhPublicKey OPTIONAL,
  reqRekey   [2]  BOOLEAN DEFAULT FALSE,
  changedKey [3]  BOOLEAN DEFAULT FALSE,
  ... }

SequenceNumber ::= INTEGER

InitializationVector ::= OCTET STRING (SIZE (16))

ClearToken3 ::= SEQUENCE {
  sigAlg       AlgorithmIdentifier {{SupportedSignatureAlgorithms}},
  version      Version DEFAULT {v1},
  assoID       AssoID OPTIONAL,
  time         TimeStamp,
  pkCert       PKCert,
  certPath     CertPath OPTIONAL,
  ... }

Signature ::= SEQUENCE {
  algo    AlgorithmIdentifier{{SupportedSignatureAlgorithms}},
  sign    OCTET STRING,
  ... }

Authenticator::= SEQUENCE {
  nonce    OCTET STRING  OPTIONAL,
  algo     AlgorithmIdentifier{{ Supported-ICV-Algorithms }},
  icv      OCTET STRING,
  ... }

HandshakeDiagnostics ::= ENUMERATED {
  no-reason-given                  (0),
  protocol-error                   (1),
  protected-protocol-not-supported (2),
  invalid-signatureAlgorithm       (3),
  unexpected-version               (4),
  hmac-algorithm-not-supported     (5),
  encryption-not-required          (6),
  encryption-required              (7),
  invalid-public-key-certificate   (8),
  invalid-certification-path       (9),
  invalid-time-value               (10),
  dhGroup-not-supported            (11),
  illegal-dhGroup-selected         (12),
  icv-algorithms-not-supported     (13),
  encrypt-algorithms-not-supported (14),
  aea-algorithms-not-supported     (15),
  invalid-attribute-certificate    (16),
  encr-mode-aea-not-supported      (17),
  ae-is-required                   (18),
  altSig-mismatch                  (19),
  aea-select-but-encryp-not-supp   (20),
  invalid-ae-algorithm             (21),
  single-ae-algorithm-required     (22),
  ae-not-used                      (23),
  invalid-encryption-algorithm     (24),
  single-encrypt-algo-required     (25),
  single-icv-algo-required         (26),
  ... }

DtDiagnostics ::= ENUMERATED {
  no-reason-given                  (0),
  protocol-error                   (1),
  unexpected-version               (2),
  encryption-not-selected          (3),
  encryption-required              (4),
--not used                         (5),
  gmac-nonce-required              (6),
  invalid-time-value               (7),
  invalid-sequence-number          (8),
  aes-init-vector-required         (9),
  unexpected-dhPublicKey           (10),
  unexpected-changedCypher         (11),
  ... }

ALGORITHM ::= CLASS {
  &Type          OPTIONAL,
  &id            OBJECT IDENTIFIER UNIQUE }
WITH SYNTAX {
  [PARMS        &Type]
  IDENTIFIED BY &id }

AlgorithmIdentifier{ALGORITHM:SupportedAlgorithms} ::= SEQUENCE {
  algorithm   ALGORITHM.&id({SupportedAlgorithms}),
  parameters  ALGORITHM.&Type({SupportedAlgorithms}{@algorithm}) OPTIONAL,
  ... }

SupportedAlgorithms ALGORITHM ::= {...}


-- Object identifier allocations

iec62351             OBJECT IDENTIFIER ::= { iso(1) standard(0) iec62351(62351) }
e2e-security         OBJECT IDENTIFIER ::= { iec62351 part4(4) }
secModule            OBJECT IDENTIFIER ::= { e2e-security module(0) }
abstract-syntax      OBJECT IDENTIFIER ::= { e2e-security abstractSyntax(1) }
appl-context         OBJECT IDENTIFIER ::= { e2e-security appl-context(2) }

/* The specifications below are only relevant for an environment where
   XML encoding will be used. It does not affect BER ncoding */

ENCODING-CONTROL XER
  GLOBAL-DEFAULTS MODIFIED-ENCODINGS
  [NAMESPACE AS "http://www.iec.ch/62351/2018/E2E_4"] ALL IN ALL, ALL

  [NOT NAMESPACE] HandshakeReq.pp 
  [ATTRIBUTE] HandshakeReq.pp 

  [NOT NAMESPACE] ClearToken1.version, ClearToken1.assoID, ClearToken1.time
  [ATTRIBUTE] ClearToken1.version, ClearToken1.assoID, ClearToken1.time

  [NOT NAMESPACE] DiffieHellmanSet.groupId
  [ATTRIBUTE] DiffieHellmanSet.groupId

  [NOT NAMESPACE] ClearToken2.version, ClearToken2.assoID, ClearToken2.time,
                  ClearToken2.seq, ClearToken2.reqRekey, ClearToken2.changedKey
  [ATTRIBUTE] ClearToken2.version, ClearToken2.assoID, ClearToken2.time,
                  ClearToken2.seq, ClearToken2.reqRekey, ClearToken2.changedKey

  [NOT NAMESPACE] ClearToken3.version, ClearToken3.assoID, ClearToken3.time
  [ATTRIBUTE] ClearToken3.version, ClearToken3.assoID, ClearToken3.time

  [NOT NAMESPACE] AlgorithmIdentifier.algorithm
  [ATTRIBUTE] AlgorithmIdentifier.algorithm

  [NAME AS "ApplData"] HandshakeReq.tbs.applData, HandshakeAcc.tbs.applData
  [NAME AS "ApplData"] ApplicationReject.tbs.applData, ApplAbort.tbs.applData
  [NAME AS "ApplData"] ClearTransfer.tbp.applData

  [NAME AS "grp"] DiffieHellmanSet.groupId
  [NAME AS "dhpk"] DiffieHellmanSet.dhPublicKey

  [NAME AS "id"] AlgorithmIdentifier.algorithm
  [NAME AS "parm"] AlgorithmIdentifier.parameters

  [BASE64] ClearToken1.pkCert
  [BASE64] ClearToken1.attCert
  [BASE64] DiffieHellmanSet.dhPublicKey
  [BASE64] CertPath.pkCert
  [BASE64] Signature.sign
  [BASE64] ClearToken3.pkCert
  [BASE64] EncrTransfer.tbp.applData
  [BASE64] ClearToken2.iv
  [BASE64] ClearToken2.rekey
  [BASE64] Authenticator.nonce
  [BASE64] Authenticator.icv

END -- E2E-Security
